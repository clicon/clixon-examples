module clixon-hello {
    yang-version 1.1;
    namespace "urn:example:hello";
    prefix he;
    revision 2019-04-17 {
	description
	    "Clixon hello world example";
    }
    container hello{
	container world{
	    presence true;
	}
    }
    grouping g2 {
        list g2 {
	    uses g1;
        }
      }
    grouping g1 {
        list g1 {
	    uses g2;
        }
      }

    list routing-table {
	key name;
	leaf name{
	    type string;
	}
	leaf family {
	    type int32;
	}
    }
    container top{
	presence true;
	uses g1;
        list routing-table {
	key name;
	leaf name{
	    type string;
	}
	leaf family {
	    type int32;
	}
    }
    }
}
