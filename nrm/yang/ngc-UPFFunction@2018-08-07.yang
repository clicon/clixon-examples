submodule ngc-UPFFunction {
    
	belongs-to ngc { prefix ngc; }
    
	import EP_RP { prefix ep-rp; revision-date "2018-07-31"; }
    import ManagedFunction { prefix mf; revision-date "2018-07-31"; }
    import nrm-types-3gpp { prefix nrm-type; revision-date "2018-07-31"; }

    description "UPFFunction derived from basic ManagedFunction";

    revision 2018-08-07 {
        description "Initial revision";
    }

    grouping UPFFunction {
        uses mf:ManagedFunction; 
        
		list pLMNId {
            min-elements "1";
            description "a list of PLMN-Id, PLMN-Id= Mobile Country Codes (MCC)|| Mobile Network Codes(MNC) ";
            config "true";
            key "MCC MNC";
            uses nrm-type:pLMNId;
        }
    		
        leaf-list tAC {
            min-elements "1";
            config "false";
        	type nrm-type:t_tAC; 
       	
        }
        
        leaf-list s-NSSAI {
            min-elements "0";
            config "true";
            description "It represents the list of S-NSSAI the managed object is capable
                    of supporting, an S-NSSAI is comprised of a SST (Slice/Service
                    type) and an optional SD (Slice Differentiator) field, (Ref. 3GPP
                    TS 23.003 [13]). ";
            reference "3GPP TS 23.003";
        	type nrm-type:t_s-NSSAI; 
        }		
       
     	list EP_N3 { uses ep-rp:EP_N4; }
     	list EP_N4 { uses ep-rp:EP_N7; }
     	list EP_N9 { uses ep-rp:EP_N10; }
     	list EP_N6 { uses ep-rp:EP_N11; }
     	list EP_S5U { uses ep-rp:EP_S5C; }
     }

}
