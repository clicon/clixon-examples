module ngran {

    namespace "urn:3gpp:tsg:sa5:nrm:ngran";
    prefix "ngran";
    
    import ManagedElement { prefix me; revision-date "2018-07-31"; }
    
    include ngran-nRCellCU;
    include ngran-nRCellDU;
    include ngran-nRSectorCarrier;
    include ngran-gNBDUFunction;
    include ngran-gNBCUCPFunction;
    include ngran-gNBCUUPFunction;
    	
    organization "3gpp SA5";
    description "Main YANG module for the NRM NG-RAN Defined gNB as ManagedElement
        (subclass of ME) for overaching all other functions supported
        ngran Define constitued MFs and EPs as container in submodule";

    revision 2018-07-27 {
        description "15.0.2";
    }


    container ManagedElement {
    	description "list constituted MF and EP below, let's discuss if umbrella ManagedElement needed for NR
    		if it's not required, we can just remove the me and keep the container below";
      uses me:ManagedElement;
      list GNBDUFunction { uses GNBDUFunction; }
      list GNBCUCPFunction { uses GNBCUCPFunction; }
      list GNBCUUPFunction { uses GNBCUUPFunction; }
    }
}
