module ManagementNode {
    namespace "urn:3gpp:tsg:sa5:nrm:ManagedElement";
    prefix "managementNode";
    import nrm-types-3gpp { prefix nrm-type; revision-date "2018-07-31"; }
    import Top { prefix top; revision-date "2018-07-31"; }
    import VsDataContainer {prefix vsData; revision-date "2018-12-18"; }
    organization "3gpp SA5";
 
    revision 2018-12-18 {
        description "15.1.0";
    }
 
	container ManagementNode {
	       	uses top:Top;
	    leaf id {
	            mandatory "true";
	            config "false";
	            description "";
	            type nrm-type:t_dn;
	        }
		leaf userLabel {
	            description "";
	            mandatory "true";
	            config "true";
	            type string;
	        }
	    leaf-list managedElements {
            description "";
            config "false";
            type nrm-type:t_dn;
        }
	    leaf vendorName {
	            mandatory "true";
	            config "false";
	            description "";
	            type string;
	        }
	    leaf locationName {
            mandatory "true";
            config "false";
            type string;
        }
	    leaf userDefinedState {
	            mandatory "true";
	            config "true";
	            description "";
	            type string;
	        }
	    leaf swVersion {
	            mandatory "true";
	            config "false";
	            description "";
	            type string;
	        }
        list vsDataContainer {
            min-elements "0";
       	    uses vsData:VsDataContainer;
        }
    }
}
