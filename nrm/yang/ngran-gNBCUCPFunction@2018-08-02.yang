submodule ngran-gNBCUCPFunction {
    
	belongs-to ngran { prefix ngran; }
    
	import EP_RP { prefix ep-rp; revision-date "2018-07-31"; }
    import ManagedFunction { prefix mf; revision-date "2018-07-31"; }
    import nrm-types-3gpp { prefix nrm-type; revision-date "2018-07-31"; }
    
    include ngran-nRCellCU;

    description "GNBCUCPFunction derived from basic ManagedFunction, for 3 split deployment mode only";

    revision 2018-08-02 {
        description "15.0.2";
    }

    grouping GNBCUCPFunction {
            uses mf:ManagedFunction; 
            
            leaf gNBCUName {
                description "PrintableString(SIZE(1..150,))";
                mandatory "false";
                config "true";
                type string {
                	length "1..150";
                }
            }
            leaf gNBId {
                description "It identifies a gNB within a PLMN. See gNB Identifier (gNB ID) of subclause 8.2 of 3GPP TS 38.300 [3]). See Global gNB ID in subclause 9.3.1.6 of 3GPP TS 38.413 [5]. ";
                mandatory "true";
                config "false";
                type uint32;
            }
			leaf gNBIdLength {
                description "It indicates the number of bits for encoding the gNB ID.";
                mandatory "true";
                config "false";
                type uint32 {
					range "22..32";
				}
            }

            list pLMNId {
                min-elements "1";
                description "a list of PLMN-Id, PLMN-Id= Mobile Country Codes (MCC)|| Mobile Network Codes(MNC) ";
                config "true";
                key "MCC MNC";
                uses nrm-type:pLMNId;
            }    		
    		choice gNB-type {
    		    case gNB {
    			    list EP-NgC { uses ep-rp:EP_NgC; }
    				list EP-XnC { uses ep-rp:EP_XnC; }
    			 }
    			 case en-gNB {
    			    container EP-X2C { uses ep-rp:EP_X2C; }
    			 }
    		  }
    		
         	  list EP_F1C { uses ep-rp:EP_F1C; }
        	  list EP_E1 { uses ep-rp:EP_E1; }
        	  
		      list NRCellCU { uses NRCellCU; }    		
     }
}
