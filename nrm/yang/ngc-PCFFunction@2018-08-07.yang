submodule ngc-PCFFunction {
    
	belongs-to ngc { prefix ngc; }
    
	import EP_RP { prefix ep-rp; revision-date "2018-07-31"; }
    import ManagedFunction { prefix mf; revision-date "2018-07-31"; }
    import nrm-types-3gpp { prefix nrm-type; revision-date "2018-07-31"; }
    import ietf-inet-types { prefix inet; revision-date "2010-09-24"; }  

    description "PCFFunction derived from basic ManagedFunction";

    revision 2018-08-07 {
        description "Initial revision";
    }

    grouping PCFFunction {
        uses mf:ManagedFunction; 
        
		list pLMNId {
            min-elements "1";
            description "a list of PLMN-Id, PLMN-Id= Mobile Country Codes (MCC)|| Mobile Network Codes(MNC) ";
            config "true";
            key "MCC MNC";
            uses nrm-type:pLMNId;
        }
    		
        leaf sBIFQDN {
            mandatory "true";
            config "true";
            description "";
            type inet:domain-name;
        }
        
        leaf-list sBIService {
            min-elements "1";
            config "false";
        	type string; 
       	
        }
 
        leaf-list s-NSSAI {
            min-elements "0";
            config "true";
            description "It represents the list of S-NSSAI the managed object is capable
                    of supporting, an S-NSSAI is comprised of a SST (Slice/Service
                    type) and an optional SD (Slice Differentiator) field, (Ref. 3GPP
                    TS 23.003 [13]). ";
            reference "3GPP TS 23.003";
        	type nrm-type:t_s-NSSAI; 
        }
		
       
     	list EP_N5 { uses ep-rp:EP_N5; }
     	list EP_N7 { uses ep-rp:EP_N7; }
     	list EP_N15 { uses ep-rp:EP_N15; }
     	list EP_N16 { uses ep-rp:EP_N16; }
     	list EP_Rx { uses ep-rp:EP_Rx; }
    	list EP_SBI_X {
            key id;
    		uses ep-rp:EP_SBI_X;
    	}
     }

}
