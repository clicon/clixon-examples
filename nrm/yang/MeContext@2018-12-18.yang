module MeContext {
    namespace "urn:3gpp:tsg:sa5:nrm:MeContext";
    prefix "meContext";
    import nrm-types-3gpp { prefix nrm-type; revision-date "2018-07-31"; }
    import Top { prefix top; revision-date "2018-07-31"; }
    organization "3gpp SA5";

    revision 2018-12-18 {
        description "Initial Version";
    }
        
    container MeContext {
       	uses top:Top;
		leaf id {
            mandatory "true";
            config "false";
            description "derived from top_";
            type nrm-type:t_dn;
        }
        leaf dnPrefix {
            mandatory "true";
            config "false";
            description "derived from domain_";
            type string;
        }
        
 }
}
