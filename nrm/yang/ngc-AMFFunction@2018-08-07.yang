submodule ngc-AMFFunction {
    
	belongs-to ngc { prefix ngc; }
    
	import EP_RP { prefix ep-rp; revision-date "2018-07-31"; }
    import ManagedFunction { prefix mf; revision-date "2018-07-31"; }
    import nrm-types-3gpp { prefix nrm-type; revision-date "2018-07-31"; }
    import ietf-inet-types { prefix inet; revision-date "2010-09-24"; }  

    description "AMFFunction derived from basic ManagedFunction";

    revision 2018-08-07 {
        description "Initial revision";
    }

    grouping AMFFunction {
        uses mf:ManagedFunction; 
        
		list pLMNId {
            min-elements "1";
            description "a list of PLMN-Id, PLMN-Id= Mobile Country Codes (MCC)|| Mobile Network Codes(MNC) ";
            config "true";
            key "MCC MNC";
            uses nrm-type:pLMNId;
        }
    		
        container aMFIdentifier {
            presence "true";
            config "true";
            description "";
            uses nrm-type:aMFI;
        }
        
        leaf sBIFQDN {
            mandatory "true";
            config "true";
            description " ";
            type inet:domain-name;
        }
        
        leaf-list sBIService {
            description "";
            min-elements "1";
            config "false";
        	type string; 
       	
        }
    		
        leaf weightFactor {
            mandatory "true";
            config "true";
            description "";
            type uint8;
        }
        
        leaf-list s-NSSAI {
            min-elements "0";
            config "true";
            description "It represents the list of S-NSSAI the managed object is capable
                    of supporting, an S-NSSAI is comprised of a SST (Slice/Service
                    type) and an optional SD (Slice Differentiator) field, (Ref. 3GPP
                    TS 23.003 [13]). ";
            reference "3GPP TS 23.003";
        	type nrm-type:t_s-NSSAI; 
        }
		
       
     	list EP_N2 { uses ep-rp:EP_N2; }
     	list EP_N8 { uses ep-rp:EP_N8; }
     	list EP_N11 { uses ep-rp:EP_N11; }
     	list EP_N12 { uses ep-rp:EP_N12; }
     	list EP_N14 { uses ep-rp:EP_N14; }
     	list EP_N15 { uses ep-rp:EP_N15; }
     	list EP_N17 { uses ep-rp:EP_N17; }
     	list EP_N20 { uses ep-rp:EP_N20; }
     	list EP_N22 { uses ep-rp:EP_N22; }
     	list EP_N26 { uses ep-rp:EP_N26; }
     	list EP_NLS { uses ep-rp:EP_NLS; }
     	list EP_NLG { uses ep-rp:EP_NLS; }
    	list EP_SBI_X {
    		uses ep-rp:EP_SBI_X;
    	}
   	
     }

}
