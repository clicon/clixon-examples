module _3gpp-5gc-nrm-amfset {
  yang-version 1.1;
  namespace urn:3gpp:sa5:_3gpp-5gc-nrm-amfset;
  prefix amfset3gpp;
  
  import _3gpp-common-yang-types { prefix types3gpp; }
  import _3gpp-common-subnetwork { prefix subnet3gpp; }
  import _3gpp-common-top { prefix top3gpp; }
  import _3gpp-common-managed-function { prefix mf3gpp; }
  
  description "This IOC represents the AMF Set which consists of some AMFs that serve a given area and Network Slice.";

  revision 2019-10-28 { reference S5-193518 ; }
  revision 2019-06-11 {
    description "Ericsson refactoring.";
  }
  
  grouping AMFSetGrp {
    uses mf3gpp:ManagedFunctionGrp;
    
    list pLMNIdList {
      description "List of at most six entries of PLMN Identifiers, but at least one (the primary PLMN Id).
                   The PLMN Identifier is composed of a Mobile Country Code (MCC) and a Mobile Network Code (MNC).";

      min-elements 1;
      max-elements 6;
      key "mcc mnc";
      uses types3gpp:PLMNId;
    }
    
    leaf-list nRTACList {
      description "List of Tracking Area Codes (legacy TAC or extended TAC) 
                   where the represented management function is serving.";
                   reference "TS 38.413 clause 9.3.3.10";
      min-elements 1;
      config false;
      type types3gpp:Tac;
    }
    
    leaf-list sNSSAIList {
      description "List of S-NSSAIs the managed object is capable of supporting.
                   (Single Network Slice Selection Assistance Information)
                   An S-NSSAI has an SST (Slice/Service type) and an optional SD 
                  (Slice Differentiator) field.";
      //conditional support only if the network slicing feature is supported.
      reference "3GPP TS 23.003";
      type types3gpp:SNssai;
    }
    
    leaf aMFRegion {
      description "The AMFRegion that the AFMSet is associated with.";
      type instance-identifier;
    }
    
    leaf-list aMFSetMemberList {
      description "List of DNs of AMFFunction instances of the AMFSet.";
      min-elements 1;
      max-elements 1;
      type types3gpp:DistinguishedName;
    }
  }
  
  augment "/subnet3gpp:SubNetwork" {
    list AMFSet {
      description "5G Core AMFSet IOC";
      reference "3GPP TS 28.541";
      key id;
      uses top3gpp:Top_Grp;
      container attributes {
        uses AMFSetGrp;
      }
      uses mf3gpp:ManagedFunctionContainedClasses;
    }
  }
}
