module _3gpp-5gc-nrm-nrffunction {
  yang-version 1.1;
  
  namespace urn:3gpp:sa5:_3gpp-5gc-nrm-nrffunction;
  prefix nrf3gpp;
  
  import _3gpp-common-managed-function { prefix mf3gpp; }
  import _3gpp-common-managed-element { prefix me3gpp; }
  import ietf-inet-types { prefix inet; }
  import _3gpp-common-yang-types { prefix types3gpp; }
  import _3gpp-5gc-nrm-nfprofile { prefix nfp3gpp; }
  import _3gpp-common-top { prefix top3gpp; }
  
  organization "3gpp SA5";
  description "This IOC represents the NRF function in 5GC.
               For more information about the NRF, see 3GPP TS 23.501 [2].";
  reference "3GPP TS 28.541";
  
  revision 2019-10-28 { reference S5-193518 ; }
  revision 2019-05-15 {
    description "initial revision";
  }
  
  grouping NRFFunctionGrp {
    uses mf3gpp:ManagedFunctionGrp;
    
    list pLMNIdList {
      description "List of at most six entries of PLMN Identifiers, but at least one (the primary PLMN Id).
                   The PLMN Identifier is composed of a Mobile Country Code (MCC) and a Mobile Network Code (MNC).";

      min-elements 1;
      max-elements 6;
      key "mcc mnc";
      uses types3gpp:PLMNId;
    }
    
    leaf sBIFQDN {
      description "The FQDN of the registered NF instance in the service-based interface.";
      type inet:domain-name;
    }
    
    leaf-list nSIIdListWrap {
      description "Set of NSI Ids. The NSI ID represents the Network Slice Instance Identifier.";
      //optional support
      type types3gpp:NsiId;
    }
    
    leaf-list sNSSAIList {
      description "List of S-NSSAIs the managed object is capable of supporting.
                   (Single Network Slice Selection Assistance Information)
                   An S-NSSAI has an SST (Slice/Service type) and an optional SD
                   (Slice Differentiator) field.";
      //optional support
      reference "3GPP TS 23.003";
      type types3gpp:SNssai; 
    }
    
    list nFProfileList {
      description "Set of NFProfile(s) to be registered in the NRF instance.";
      //optional support
      key nfInstanceID;
      uses nfp3gpp:NFProfileGrp;
    }
  }
  
  augment "/me3gpp:ManagedElement" {
    list NRFFunction {
      description "5G Core NRF Function";
      reference "3GPP TS 28.541";
      key id;
      uses top3gpp:Top_Grp;
      container attributes {
        uses NRFFunctionGrp;
      }
      uses mf3gpp:ManagedFunctionContainedClasses;
    }
  }
}
