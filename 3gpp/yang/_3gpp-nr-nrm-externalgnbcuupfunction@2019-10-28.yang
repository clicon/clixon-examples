module _3gpp-nr-nrm-externalgnbcuupfunction {
  yang-version 1.1;
  namespace "urn:3gpp:sa5:_3gpp-nr-nrm-externalgnbcuupfunction";
  prefix "extgnbcuup3gpp";

  import _3gpp-common-managed-function { prefix mf3gpp; }
  import _3gpp-nr-nrm-nrnetwork { prefix nrnet3gpp; }
  import _3gpp-common-subnetwork { prefix subnet3gpp; }
  import _3gpp-common-top { prefix top3gpp; }

  organization "3GPP SA5";
  description "Defines the YANG mapping of the ExternalGNBCUUPFunction
    Information Object Class (IOC), that is part of the NR Network
    Resource Model (NRM).";
  reference "3GPP TS 28.541 5G Network Resource Model (NRM)";

  revision 2019-10-28 { reference S5-193518 ; }
  revision 2019-06-17 {
    description "Initial revision";
  }

  grouping ExternalGNBCUUPFunctionGrp {
    description "Represets the ExternalGNBCUUPFunction IOC.";
    reference "3GPP TS 28.541";   
    uses mf3gpp:ManagedFunctionGrp; 
            
    leaf gNBId {
      description "Identifies a gNB within a PLMN.";
      reference "gNB Identifier (gNB ID) in 3GPP TS 38.300, Global gNB ID
        in 3GPP TS 38.413";
      mandatory true;
      type int64 { range "0..4294967295"; }
    }

    leaf gNBIdLength {
      description "Indicates the number of bits for encoding the gNB ID.";
      reference "gNB ID in 3GPP TS 38.300, Global gNB ID in 3GPP TS 38.413";
      mandatory true;
      type int32 { range "22..32"; }
    }
  }

  grouping ExternalGNBCUUPFunctionWrapper {
    list ExternalGNBCUUPFunction {
      description "Represents the properties, known by the management function,
        of a GNBCUUPFunction managed by another management function.";
      reference "3GPP TS 28.541";
      key id;
      uses top3gpp:Top_Grp;
      container attributes {
        uses ExternalGNBCUUPFunctionGrp;
      }
      uses mf3gpp:ManagedFunctionContainedClasses;
    }
  } 
  
  augment "/subnet3gpp:SubNetwork" {
    if-feature subnet3gpp:ExternalsUnderSubNetwork ;
    uses ExternalGNBCUUPFunctionWrapper;
  }

  augment "/nrnet3gpp:NRNetwork" {
    if-feature nrnet3gpp:ExternalsUnderNRNetwork;
    uses ExternalGNBCUUPFunctionWrapper;
  }	
}
